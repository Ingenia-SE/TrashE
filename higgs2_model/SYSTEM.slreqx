# SYSTEM

## -: Propulsion System (Functional)

### SYS01: Maximum Speed (Functional)
The system maximum speed shall be limited to 2 m/s.

### SYS02: Maximum Torque (Functional)
The system shall have a maximum torque at least of 50 Nm, to improve Higgs 1.0.

### SYS03: Maximum Acceleration (Functional)
The system shall accelerate 5 m/s^2 .

### SYS04: Power (Functional)
The system shall have a power of at least 100 W.

### SYS26: Reliability (Functional)
The propulsion system shall last for 5 years at least.

### SYS27: Weight (Functional)
The group of elements of the propulsion system shall have a maximum mass of 2 kg.

## -: Perception System (Functional)

### SYS05: Resolution (Functional)
The system shall have a 20 Mpx camera.

### SYS07: Reliability (Functional)
The perception system should last for 2 years.

### SYS08: Weight (Functional)
The perception system shall have a maximum mass of 1 kg.

### SYS21: Avoid Obstacles (Functional)
The system shall include software to avoid obstacles.

### SYS25: Current Sensors (Functional)
The system shall have current sensors on the motors.

## -: Navigation System (Functional)

### SYS09: Path Planning (Functional)
The system shall be able to generate its own routes.

### SYS10: Location (Functional)
The system shall be able to locate its position in real time with an accuracy of +/- 0.3 m.

### SYS11: Route Tracking (Functional)
The system shall be able to follow the path planned with a maximum deviation of 0.4 m.

### SYS12: Reliability (Functional)
The navigation system should last for 2 years.

### SYS13: Weight (Functional)
The group of elements of the navigation system shall have a maximum mass of 1 kg.

### SYS06: Autonomy (Functional)
The system shall be able to move autonomously.

## -: Energy System (Functional)

### SYS14: Autonomy (Functional)
The system shall have a battery capacity of at least 22 kWh, to improve the battery duration of the Higgs 1.0.

### SYS15: Weight (Functional)
The energy system shall have a maximum mass of 1 kg.

### SYS16: Recharge time (Functional)
Batteries shall be fully recharged in 2 hour.

## -: Expected Lifetime (Container)
-

### SYS17: Battery Life (Functional)
The battery shall operate without failure for at least 1 year.

### SYS18: Sensors Life (Functional)
Sensors shall operate without failure for at least 1 year.

### SYS19: Mechanic Life (Functional)
The mechanic elements shall operate without failure for at least 1 month.

## SYS20: Maximum Payload (Functional)
The system shall have the capacity to carry a maximum load of 40 kg.

## SYS22: Generated Noise (Functional)
The system shall operate without exceeding 40 dB.

## -: Software (Container)

### SYS23: ROS2 (Functional)
All the systems shall be operated by ROS2.

### SYS24: Ignition Gazebo (Functional)
All the systems shall be simulated on Ignition Gazebo by request of the stakeholders (Esther Aguado).

## SYS28: Quick Coupling Mechanism (Functional)
The system shall have a quick coupling mechanism to quickly change between two experiments.
