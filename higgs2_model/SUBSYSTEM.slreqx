# SUBSYSTEM

## -: Perception (Container)

### SUB07: LIDAR (Functional)
The system shall have a LIDAR.

### SUB08: Pulsed Sensors (Functional)
The system shall have pulsed sensors.

### SUB09: RGBD and Infrared Camera (Functional)
The system shall have a RGBD and infrared camera with a 2 DOF high precision and torque actuator for the orientation of the camera.

## -: Communication (Container)

### SUB03: DGPS (Functional)
The system should have a radio antenna for DGPS.

### SUB04: GPS (Functional)
The system shall include a high performance GPS.

## -: Supporting (Container)

### SUB05: Wireless Network (Functional)
The system shall include a wireless network for communications with the wireless local network in the ASLab.

### SUB06: User Terminal (Functional)
The system shall include a user terminal.

### SUB14: Information Capture (Functional)
The system shall collect all important information for future experiments.

## -: Motion (Container)

### SUB11: Engines (Functional)
The system shall have 4 Pittman motors GM9236E204.

## -: Control (Container)

### SUB02: Onboard Computer (Functional)
The system shall include an onboard computer.

### SUB01: Base Platform (Functional)
The system shall include the Pioneer 2-AT8 platform.

## -: Power (Container)

### SUB12: Battery (Functional)
The system shall use 3 batteries of 12 VDC 7 Ah-h.

### SUB13: Power Board (Functional)
The system shall have a board for controlling power to other devices.
