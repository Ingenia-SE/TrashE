# STAKEHOLDERS

## ST00: Main Objective (Informational)
The system shall serve as a platform for research and development for the ASLab projects of several investigators.

## -: Modular capacity (Container)
The system shall have the capacity to be modular in order to be usable for cognitive robotics experiments.

### ST33: Additional Hardware (Informational)
The system shall be able to change the hardware for the experiment you want to perform.

### ST34: Additional Software (Informational)
The system shall be able to change the software for the experiment you want to perform.

### ST35: External software (Functional)
The system shall accept interaction for external software.

### ST36: Quick Rotatory Mission (Functional)
The system shall be able to switch quickly between two experiments.

## ST02: Autonomous Battery Charge (Informational)
The system shall charge itself autonomously.

## -: Autonomous Navigation (Container)
The system shall navigate autonomously in its surroundings.

### ST04: Position (Informational)
The system shall know its position.

### ST05: Velocity (Informational)
The system shall know its speed.

### ST20: Safety (Informational)
The system shall be careful of their surroundings due to the presence of people or animals. It shall avoid risks.

### ST24: Adaptability (Informational)
The system shall adapt to changes of the floor.

## -: Reliability (Container)

### ST11: MTBR (Informational)
The mean time before repair shall be more than 2 years.

### ST12: MTBF (Informational)
The mean time before failure shall be more than 12 months.

### ST13: Waterproof (Informational)
The system shall resist raindrop.

### ST14: Dustproof (Informational)
The system shall resist the ingress of dust.

### ST15: Impact Resistant (Informational)
The system shall be tough.

## ST16: Noise (Informational)
The system shall be silent, within the limits required by the regulations, i.e. less than a leaf blower.

## -: Communication (Container)

### ST17: User Interface (Informational)
The system shall have a user interface.

### ST18: Data Capture and Monitoring (Informational)
Users shall have the control of the system.
The system shall collect information related to different and future experiments.

### ST19: WIFI (Informational)
The system shall allow communication via wifi.

## -: Perception (Container)

### ST21: Avoid Obstacles (Informational)
The system shall include obstacle avoidance software.

### ST06: Incident Warning (Informational)
The system shall report if there is an incident.
Incident is to be understood as some situation that may cause damage in the robot or in the users of the robot.

### ST23: Stuck Detection (Informational)
The system shall detect if it becomes trapped without the need for localisation.

### ST29: Location Sensors (Informational)
The system shall have location sensors to achieve a very precise localization.
- Rationale: Feedback from Esther Aguado

## -: Feasibility (Container)

### ST25: Deadlines (Informational)
The reconditioning of the robot shall spend less than 1000 h.

### ST26: Cost (Informational)
The cost of the components shall be lower than INGENIA SE budget.

### ST27: Stock (Informational)
The stock of the components shall be available.

## -: Interaction with objects (Container)

### ST07: Loading Capacity (Informational)
The system shall have the capacity to carry loads.

### ST08: Unloading Capacity (Informational)
The system shall have the capacity to unload loads.

### ST28: Collection (Informational)
The system may collect objects from the floor.

## ST30: Operating Time (Informational)
The system shall have a battery that operates for at least 2 h.
- Rationale: Feedback from Esther Aguado

## -: Fault Injection (Container)
The system shall be able to introduce artificial injection of disturbances to create experimental fault scenarios for evaluation.

### ST31: Main Actuators (Functional)
The system shall allow the main actuators to be disconnected through code.
- Rationale: Feedback from Esther Aguado

### ST32: Sensors (Functional)
The system shall allow the sensors to be disconnected through code.
- Rationale: Feedback from Esther Aguado

## ST09: Hardware for Autonomous Vehicles (Informational)
The system shall include a state of the art SoC for automated driving.

## ST10: Reuse (Informational)
The new system shall use as many as possible of the elements from the previous system.

## ST37: UGV - UAV Collaboration (Informational)
The system should be able to cooperate with the drone in the collection of cans from the "pérgola".

## ST38: Experiment Replication (Functional)
The system shall have the ability to replicate experiments.

## ST39: Documentation for Experimenters (Functional)
The system shall generate documentation and procedures to be used by future experimenters.
