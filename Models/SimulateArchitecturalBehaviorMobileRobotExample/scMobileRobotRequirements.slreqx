# scMobileRobotRequirements

## -: Endurance (Container)

### SYSTEM-REQ-01: Battery Capacity (Functional)
The robot shall have a battery capacity sufficient for a minimum of of 10 hours of continous operation.

### SYSTEM-REQ-02: Battery Charge Time (Functional)
The robot shall be able to charge itself to full capacity in a maximum of 2 hours.

## -: Payload and Speed (Container)

### SYSTEM-REQ-03: Maximum Payload (Functional)
The robot shall support a maximum payload of 500 kg.

### SYSTEM-REQ-04: Nominal Operating Speed with Payload (Functional)
The robot shall be able to operate at 1 m/s with a full payload.

### SYSTEM-REQ-13: Motor Type (Functional)
The robot shall use brushless DC motors for propulsion and payload handling.

## -: Autonomy (Container)

### SYSTEM-REQ-05: Self-Localization (Functional)
The robot must be able to determine its current position within 0.1 m.

### SYSTEM-REQ-06: Path Generation (Functional)
The robot shall automatically generate a path from its current position to a newly specified position.

### SYSTEM-REQ-07: Path Following (Functional)
The robot shall follow a generated path with a maximum deviation of ±0.1 m.

### SYSTEM-REQ-08: Collision Avoidance (Functional)
The robot shall be able to avoid collisions with stationary and mobile objects when operating at maximum speed.

### SYSTEM-REQ-12: Path Gen Time (Functional)
The robot shall generate a path in less than 0.3 seconds.

### SYSTEM-REQ-09: Charging Station Location (Functional)
The robot shall be able to locate its own charging station and set it as a target

## -: Life Expectancy (Container)

### SYSTEM-REQ-10: Sensor Life (Container)
The robot sensors shall be able to operate without failing for 2 years.

### SYSTEM-REQ-09: Battery Life (Functional)
The robot battery shall be able to operate without failing for 2 years.

### SYSTEM-REQ-11: Mechanical Component Life (Functional)
The robot mechanical components shall have a life expectancy of 6 yrs under normal operation.
