# scMobileRobotSubsystemRequirements

## -: Battery (Functional)
This section contains low-level battery requirements.

### BATTERY-REQ-01: Battery Capacity (Functional)
The battery shall have a capacity of 2.5 kWh.

### BATTERY-REQ-02: Charging (Functional)
The battery charging station shall have a minimum charging current of 3 amperes.

## -: Structure (Functional)
This section contains structural requirements for the robot.

### STRUCT-REQ-01: Maximum Strength (Functional)
The structure must support a maximum robot weight of 1650 kg.
- Rationale: ((Dry Weight of 50 kg + Max Payload of 500 kg)* Safety Factor of 3)

## -: Propulsion (Functional)
This section contains requirements for the robot propulsion system.

### MOTOR-REQ-01: Motor Power (Functional)
The motor shall have a maximum power output of at least 0.2 kW.

### MOTOR-REQ-02: Motor Speed (Functional)
The motor shall have a top speed of at least 2000 rpm.

## -: Component Life (Functional)

### LIFE-REQ-01: LIDAR Life Expectancy (Functional)
The lidar camera shall have a minimum life expectancy of 21,900 hours.
- Rationale: 20 hours per day of operation * 365 days per year * 3 years MTBF

### LIFE-REQ-02: RGB Camera Life Expectancy (Functional)
The RGB camera shall have a minimum life expectancy of 73 hours.
- Rationale: RGB camera is only used for charging station alignment so:
  Approximately 2 minutes to align twice a day so 4 minutes per day total.
  4 minutes per day * (1/60 hours per minute) * 365 days per year * 3 years MTBF

### LIFE-REQ-03: Position Encoder Life Expectancy (Functional)
The position encoder shall have a minimum life expectancy of 200,000 cycles.
- Rationale: [maxEncoderCyclesPerDay*daysPerYear*MTBF]

### LIFE-REQ-04: Motor Life (Functional)
The motor shall have a minimum life expectancy of 200,000 cycles.
- Rationale: [maxMotorCyclesPerDay*daysPerYear*MTBF]

### LIFE-REQ-05: Battery Life (Functional)
The battery shall be able to withstand 1,460 full charge/discharge cycles before needing to be replaced.
- Rationale: [dischargeCyclesPerDay*daysPerYear*MTBR]

## -: Path Generation (Functional)

### PATH-REQ-01: Path Gen Algorithm (Functional)
The path generation function shall create a path for the robot starting from the end position and working backwards to the robot's current position.

### PATH-REQ-02: Automatic Path Regeneration (Functional)
The path generation function shall automatically generate a new path when the current path will result in an object collision.

## -: Position Determination (Functional)

### POS-REQ-02: Kalman Filter (Functional)
The position determination function shall use a kalman filter to determine the robot position.

## -: Controller (Functional)

### CTRL-REQ-01: Controller CPU Speed (Functional)
The controller shall operate at a frequency of 2 GHz.

### CTRL-REQ-02: Controller Memory (Functional)
The controller shall have 2 GB of Random Access Memory.

### CTRL-REQ-03: Controller Disk Space (Functional)
The controller shall have a storage capacity of 32 GB.
